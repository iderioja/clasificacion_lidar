FME workspace lidar_process_ndvi.fmw

Parameters:
- DestDataset_LAS = D:\salida_classify_ndvi_1x1   # Destination ASPRS LAS Folder
- SourceDataset_LAS = D:\597000_4676000_merge.laz   # Source ASPRS LAS File(s)

Readers:
- LAS_1: LAS from $(SourceDataset_LAS)

Writers:
- LAS_2: LAS to $(DestDataset_LAS)

Note: Fichero MERGE / Contiene el componente 'cat_sio'
LAS (reader LAS_1)
    -> PointCloudConsumer
Note: PointCloudConsumer, permite operar con toda / la nube de puntos sin romperla
PointCloudConsumer
    BLOCK_SIZE = 10000
    -> PointCloudComponentAdder
Note: Añadimos nuevos componentes: / ndvi / height
PointCloudComponentAdder
    COMPONENTS_TO_ADD = ndvi,Real32,0,height,Real32,0
    -> PointCloudExpressionEvaluator_2
Note: Cálculo de height: / Convertimos 'user_data' (decímetros) / en height, pasado a metros
PointCloudExpressionEvaluator_2
    EXPRESSION_TABLE = height Auto @floor(@Component(user_data)/10)
    RESULT -> PointCloudExpressionEvaluator
Note: Cálculo del NDVI
Note: Los clasificados como vegetación alta : no se modifican nunca
PointCloudExpressionEvaluator
    EXPRESSION_TABLE = ndvi Auto (@Component(color_red)-@Component(color_green))/(@Component(color_red)+@Component(color_green))
    RESULT -> PointCloudFilter
Note: Filtro / cat_sio
PointCloudFilter
    FILTER_TABLE = EXPRESSION_LIST @Component(cat_sio) !=3  && @Component(cat_sio) !=4 && @Component(cat_sio) !=6 ; @Component(cat_sio) == 3  || @Component(cat_sio) == 4  || @Component(cat_sio) == 6 FILTER_ATTRIBUTE __pc_internal_filter_attribute__ FILTER_ATTRIBUTE_VALUES_LIST cat_sio != 3 && cat_sio ! = 4 ; cat_sio == 3  || cat_sio == 4 || cat_sio == 6
    OUTPUT_UNFILTERED_POINTS = No
    cat_sio != 3 && cat_sio ! = 4 -> PointCloudFilter_2
    cat_sio == 3 || cat_sio == 4 || cat_sio == 6 -> PointCloudFilter_3
Note: 0 Created, never classified / 1 Unclassified / 2 Ground / 3 Low Vegetation / 4 Medium Vegetation / 5 High Vegetation / 6 Building / 7 Low Point (noise) / 8 Model Key-point (mass point) / 9 Water / 10 Reserved for ASPRS Definition / 11 Reserved for ASPRS Definition / 12 Overlap Points / 13-31 Reserved for ASPRS Definition
Note: RI; ratio index / VARI Visible atmospherically resistant index
Note: No urbanos / SIOSE
Note: CLASIFICACIÓN VEGETACIÓN: BAJA, MEDIA, ALTA / The American Society for Photogrammetry and Remote Sensing (ASPRS) classifies lidar points into three layers: / low vegetation (0.5 m <height<= 2.0 m), medium vegetation (2.0 <height<= 5.0 m), high vegetation (5.0 <height) / (ASPRS, 2008) / Clasificación ASPRS: / argumento += " -classify_between 0.5 2.0 3 " / argumento += " -classify_between 2.0 5 4 " / argumento += " -classify_between 5 100.0 5 " / Clasificación IGN: / argumento += " -classify_between 0 0.5 3 " / argumento += " -classify_between 0.5 3 4 " / argumento += " -classify_between 3 100.0 5 " / Clasificación (Otra clasificación): / argumento += " -classify_between 0.3 1.3 3 " / argumento += " -classify_between 1.3 3.5 4 " / argumento += " -classify_between 3.5 100.0 5 "
PointCloudFilter_2
    FILTER_TABLE = EXPRESSION_LIST @Component(classification) == 6 && @Component(ndvi) < 0.2 && @Component(number_of_returns) == 1 ; @Component(classification) == 6 && @Component(ndvi) < 0.2 && @Component(number_of_returns) > 1 && (@Component(height) >=0 && @Component(height) < 0.5) ; @Component(classification) == 6 && @Component(ndvi) < 0.2 && @Component(number_of_returns) > 1 && (@Component(height) >=0.5 && @Component(height) < 3) ; @Component(classification) == 6 && @Component(ndvi) < 0.2 && @Component(number_of_returns) > 1 && (@Component(height) >=3 && @Component(height) < 100) ; (@Component(classification) == 6 && @Component(ndvi) > 0.2) && (@Component(height) >=0 && @Component(height) < 0.5) ; (@Component(classification) == 6 && @Component(ndvi) > 0.2) && (@Component(height) >=0.5 && @Component(height) <3) ; (@Component(classification) == 6 && @Component(ndvi) > 0.2) && (@Component(height) >=3 && @Component(height) < 100) ; @Component(classification) == 0 FILTER_ATTRIBUTE __pc_internal_filter_attribute__ FILTER_ATTRIBUTE_VALUES_LIST clasificación 6 ; clasificación 3 ; clasificación 4 ; clasificación 5 ; clasificación 3 ; clasificación 4 ; clasificación 5 ; clasificación 0
    OUTPUT_UNFILTERED_POINTS = Yes
    clasificación 6 -> PointCloudExpressionEvaluator_7
    clasificación 3 -> PointCloudExpressionEvaluator_8
    clasificación 4 -> PointCloudExpressionEvaluator_9
    clasificación 5 -> PointCloudExpressionEvaluator_10
    clasificación 0 -> PointCloudExpressionEvaluator_15
    <UNFILTERED> -> PointCloudComponentRemover_2
PointCloudExpressionEvaluator_7
    EXPRESSION_TABLE = classification Auto 6
    RESULT -> PointCloudComponentRemover_2
PointCloudExpressionEvaluator_8
    EXPRESSION_TABLE = classification Auto 3
    RESULT -> PointCloudComponentRemover_2
PointCloudExpressionEvaluator_9
    EXPRESSION_TABLE = classification Auto 4
    RESULT -> PointCloudComponentRemover_2
PointCloudExpressionEvaluator_10
    EXPRESSION_TABLE = classification Auto 5
    RESULT -> PointCloudComponentRemover_2
PointCloudExpressionEvaluator_15
    EXPRESSION_TABLE = classification Auto 1
    RESULT -> PointCloudComponentRemover_2
Note: Urbano / SIOSE
Note: Los puntos no clasificados (classification=0), se clasifican la categoría / Unclassified (classification=1).
PointCloudFilter_3
    FILTER_TABLE = EXPRESSION_LIST (@Component(classification) == 6) ; @Component(classification) == 0 FILTER_ATTRIBUTE __pc_internal_filter_attribute__ FILTER_ATTRIBUTE_VALUES_LIST clasificación 6 ; clasificación 0
    OUTPUT_UNFILTERED_POINTS = Yes
    clasificación 6 -> PointCloudFilter_5
    clasificación 0 -> PointCloudExpressionEvaluator_16
    <UNFILTERED> -> PointCloudFilter_3__UNFILTERED_
PointCloudFilter_5
    FILTER_TABLE = EXPRESSION_LIST @Component(ndvi) < 0.2 ; @Component(ndvi) >= 0.2 FILTER_ATTRIBUTE __pc_internal_filter_attribute__ FILTER_ATTRIBUTE_VALUES_LIST ndvi < 0.2 ; ndvi >= 0.2
    OUTPUT_UNFILTERED_POINTS = No
    ndvi < 0.2 -> PointCloudFilter_7
    ndvi >= 0.2 -> PointCloudFilter_9
PointCloudFilter_7
    FILTER_TABLE = EXPRESSION_LIST (@Component(number_of_returns) < 3) FILTER_ATTRIBUTE __pc_internal_filter_attribute__ FILTER_ATTRIBUTE_VALUES_LIST clasificación 6
    OUTPUT_UNFILTERED_POINTS = Yes
    clasificación 6 -> PointCloudExpressionEvaluator_11
    <UNFILTERED> -> PointCloudFilter_9
PointCloudExpressionEvaluator_11
    EXPRESSION_TABLE = classification Auto 6
    RESULT -> PointCloudComponentRemover_2
PointCloudFilter_9
    FILTER_TABLE = EXPRESSION_LIST (@Component(height) >=0 && @Component(height) <0.5) ; (@Component(height) >=0.5 && @Component(height) < 3) ; (@Component(height) >=3 && @Component(height) < 100) FILTER_ATTRIBUTE __pc_internal_filter_attribute__ FILTER_ATTRIBUTE_VALUES_LIST clasificación 3 ; clasificación 4 ; clasificación 5
    OUTPUT_UNFILTERED_POINTS = Yes
    clasificación 3 -> PointCloudExpressionEvaluator_12
    clasificación 4 -> PointCloudExpressionEvaluator_13
    clasificación 5 -> PointCloudExpressionEvaluator_14
    <UNFILTERED> -> PointCloudFilter_9__UNFILTERED_
PointCloudExpressionEvaluator_12
    EXPRESSION_TABLE = classification Auto 3
    RESULT -> PointCloudComponentRemover_2
PointCloudExpressionEvaluator_13
    EXPRESSION_TABLE = classification Auto 4
    RESULT -> PointCloudComponentRemover_2
PointCloudExpressionEvaluator_14
    EXPRESSION_TABLE = classification Auto 5
    RESULT -> PointCloudComponentRemover_2
Note: PointCloudComponentRemover_2 : Input
PointCloudFilter_9__UNFILTERED_: Junction
    -> PointCloudComponentRemover_4
Note: PointCloudFilter_9 : <Unfiltered>
PointCloudComponentRemover_4: Junction
    -> PointCloudComponentRemover_2
PointCloudExpressionEvaluator_16
    EXPRESSION_TABLE = classification Auto 1
    RESULT -> PointCloudComponentRemover_2
Note: PointCloudComponentRemover_2 : Input
PointCloudFilter_3__UNFILTERED_: Junction
    -> PointCloudComponentRemover_5
Note: PointCloudFilter_3 : <Unfiltered>
PointCloudComponentRemover_5: Junction
    -> PointCloudComponentRemover_2
Note: Eliminamos el componente 'cat_sio'
PointCloudComponentRemover_2
    COMPONENTS_TO_REMOVE = cat_sio,height,ndvi
    -> PointCloudCombiner
PointCloudCombiner
    SPACING = 1.0
    ACCUM_ATTRS_NAME = Get Attributes From One Representative Feature
    EXTRACT_RASTER_NODATA_NAME = No
    -> LAS (writer LAS_2)
LAS (writer LAS_2)
