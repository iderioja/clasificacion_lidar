FME workspace lidar_process_classification.fmw

Parameters:
- SourceDataset_LAS = D:\597000_4676000.laz   # Source ASPRS LAS File(s)
- SourceDataset_ESRISHAPE_3 = D:\siose_lidar_ccaa_cuadricula_lidar.shp   # Source Esri Shapefile(s)

Readers:
- LAS_1: LAS from $(SourceDataset_LAS) in ETRS89.UTM-30N
- ESRISHAPE_1: ESRISHAPE from $(SourceDataset_ESRISHAPE_3) in ETRS89.UTM-30N

Note: Capa SISOSE con CCAA limitrofes / con la extensión de la cuadricula LIDAR
siose_lidar_ccaa_cuadricula_lidar (reader ESRISHAPE_1)
    attributes: cat_sio char(200), _lidar char(200), city short
    -> Bufferer
Note: Bufferer 10 m: En el corte se considera un buffer de 5 m / para que incluya puntos de zonas limitrofes. / Tenga referencia de puntos cercanos
Bufferer
    CAP_STYLE = Square
    INTERP_SEGMENTS = 8
    OFFSET = 5
    BUFFERED -> Clipper [CLIPPER]
Note: ENTRADA importante archivo LAZ
Note: LAZ entrada: / * Transformado a geoidales con el proceso de FME / * Archivo reescalado / comando las2las cambiar la escala a 0.01 / -rescale 0.01 0.01 0.01 / * Puntos solapados se clasifican en la clase 12 / lasoverage-step 1
Note: Parámetros por clases: lasground / --------------------------------- / Clase Step Spike Offset Standard deviation / City (3) 25 0.50 0.05 1 comando lasground_new / Urbana (3) 10 1 0.05 1 / Casas aisladas (4) 8 1 0.05 1 / Bosques (1) 5 0.50 0.2 1 -fine / Bosques doble clas: 1 1 0.05 1 / Flat terrain (2,5) 10 1 0.05 1 / Industrial (6) 30 0.50 0.05 1
Note: Parámetros por clases: lasclassify / --------------------------------- / Clase Step Planar Ground Offset / Ciudad (Logroño) / Urbana (3) 2 0.1 2 / Casas aisladas (4) 2 0.1 2 / Bosques (1) 2 0.4 2 / Bosques doble clas: / Flat terrain (2,5) 3 0.1 2 / Industrial (6) 2 0.3 3 / Agua(9)
Note: CLASIFICACIÓN VEGETACIÓN: BAJA, MEDIA, ALTA / The American Society for Photogrammetry and Remote Sensing (ASPRS) classifies lidar points into three layers: / low vegetation (0.5 m <height<= 2.0 m), medium vegetation (2.0 <height<= 5.0 m), high vegetation (5.0 <height) / (ASPRS, 2008) / Clasificación ASPRS: / argumento += " -classify_between 0.5 2.0 3 " / argumento += " -classify_between 2.0 5 4 " / argumento += " -classify_between 5 100.0 5 " / Clasificación IGN: / argumento += " -classify_between 0 0.5 3 " / argumento += " -classify_between 0.5 3 4 " / argumento += " -classify_between 3 100.0 5 " / Clasificación (Otra clasificación): / argumento += " -classify_between 0.3 1.3 3 " / argumento += " -classify_between 1.3 3.5 4 " / argumento += " -classify_between 3.5 100.0 5 "
LAS (reader LAS_1)
    -> Clipper [CLIPPEE]
Note: CLASES SIOSE: / bosques 1 / matorral 2 / pasto y prado 2 / cultivos herbaceos 2 / cultivos leñosos 2 / urbanos 3 / casas aisladas 4 / roquedos 5 / industrial 6 / agua 7
Clipper
    ATTR_ACCUM_MODE = Merge Clipper
    CREATE_AGGREGATES = Yes
    CLIP_TYPE = Multiple Clippers
    CLIPPED_ATTR = _clipped
    CONNECT_Z_MODE = First Wins
    ATTR_CONFLICT_RES = Use Clippee
    PRESERVE_CLIPPEE_EXTENTS = No
    LINES_AS_SEGMENTS = No
    BOUNDARY_CASES = Treat as Inside
    INSIDE -> PointCloudCombiner
Note: Combine points group by code_06 (cat_sio)
PointCloudCombiner
    GROUP_BY = cat_sio
    EXTRACT_RASTER_NODATA_NAME = No
    SPACING = 1.0
    ACCUM_ATTRS_NAME = Get Attributes From One Representative Feature
    -> PointCloudFilter
Note: Filtrado cat_sio: / 1 bosque / 2,5 prados / 3 Urbana / 4 casas aisladas / 6 industrial / 7 Agua
PointCloudFilter
    FILTER_TABLE = EXPRESSION_LIST @Value(cat_sio) == 1 ; @Value(cat_sio) ==  5 ; @Value(cat_sio) ==  2 ; @Value(cat_sio) ==  3 ; @Value(cat_sio) ==  4 ; @Value(cat_sio) ==  6 ; @Value(cat_sio) == 7 FILTER_ATTRIBUTE __pc_internal_filter_attribute__ FILTER_ATTRIBUTE_VALUES_LIST 1 ; 5 ; 2 ; 3 ; 4 ; 6 ; 7
    OUTPUT_UNFILTERED_POINTS = Yes
    1 -> StringConcatenator
    5 -> StringConcatenator_2
    2 -> StringConcatenator_2
    3 -> PointCloudFilter_2
    4 -> StringConcatenator_4
    6 -> StringConcatenator_5
    7 -> PointCloudExpressionEvaluator_12
Note: bosque
StringConcatenator
    VAL_ATTR = _filename
    ACTION = Create New Attribute
    PARM_LINE = @Value(fme_basename)_siose1
    -> PointCloudComponentAdder_4
Note: cat_sio
PointCloudComponentAdder_4
    COMPONENTS_TO_ADD = cat_sio,Int32,@Value(cat_sio)
    -> FeatureWriter_2 [File1]
FeatureWriter_2
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,DESTINATION_DATASETTYPE_VALIDATION,Yes,COORDINATE_SYSTEM_GRANULARITY,FEATURE,VERSION,1.2,USER_COMPONENTS,cat_sio
    FEATURE_TYPE_LIST_ATTR = _feature_type
    TOTAL_FEATURES_WRITTEN_ATTR = _total_features_written
    DATASET_ATTR = _dataset
    DATASET = C:\Trabajo_Ana\proceso_las_rioja\temp
    SUMMARY -> PythonCaller_2
Note: GROUND / HEIGHT / CLASSIFY
PythonCaller_2
    PYTHONSYMBOL = processFeature
    PYTHONSOURCE:
      import fme
      import fmeobjects
      from subprocess import call


      # Template Function interface:
      # When using this function, make sure its name is set as the value of
      # the 'Class or Function to Process Features' transformer parameter
      def processFeature(feature):
          fichero_entrada = feature.getAttribute("_feature_type{0}.name") + ".laz"

          ruta_fichero_entrada = "c:/Trabajo_Ana/proceso_las_rioja/temp/" + fichero_entrada
          ruta_salida_ground = "c:/Trabajo_Ana/proceso_las_rioja/salida_ground/"
          ruta_salida_height = "c:/Trabajo_Ana/proceso_las_rioja/salida_height/"
          ruta_salida_classify = "c:/Trabajo_Ana/proceso_las_rioja/salida_classify/"

          ruta_fichero_entrada = ruta_fichero_entrada.replace("\/", "\\")
          print(ruta_fichero_entrada)

          num_cores = 3

      # lasground
          argumento = "lasground -i " + ruta_fichero_entrada
          argumento += " -odir " + ruta_salida_ground
          argumento += " -olaz "
          argumento += " -step 5 "
          argumento += " -stddev 1 "
          argumento += " -offset 0.2 "
          argumento += " -spike 0.50 "
          argumento += " -fine "
          argumento += " -ignore_class 7 12 "
          argumento += " -non_ground_unchanged "
          # argumento += " -cores " + str(num_cores)

          resultado = call(argumento)
          if(resultado == 0):
              print("ground correcto")
          else:
              print("ground fallido")

      # lasheight
          argumento = "lasheight -i " + ruta_salida_ground + fichero_entrada
          argumento += " -odir " + ruta_salida_height
          argumento += " -olaz "
          argumento += " -classify_below -0.5 7 "
          argumento += " -classify_above 100.0 7 "
          argumento += " -classify_between 0 0.5 3 "
          argumento += " -classify_between 0.5 3 4 "
          argumento += " -classify_between 3 100.0 5 "
          argumento += " -ignore_class 7 12 "
          argumento += " -store_in_user_data "
          # argumento += " -cores " + str(num_cores)

          resultado = call(argumento)
          if(resultado == 0):
              print("height correcto")
          else:
              print("height fallido")

       # lasclassify
          argumento = "lasclassify -i " + ruta_salida_height + fichero_entrada
          argumento += " -odir " + ruta_salida_classify
          argumento += " -olaz "
          argumento += " -step 2 "
          argumento += " -planar 0.4 "
          argumento += " -ground_offset 2 "
          argumento += " -ignore_class 7 12 "
          # argumento += " -cores " + str(num_cores)

          resultado = call(argumento)
          if(resultado == 0):
              print("classify correcto")
          else:
              print("classify fallido")

          pass
    -> FeatureHolder
Note: aplicar parámetros lasground de city
StringConcatenator_2
    VAL_ATTR = _filename
    ACTION = Create New Attribute
    PARM_LINE = @Value(fme_basename)_siose2_5
    -> PointCloudComponentAdder_3
Note: cat_sio
PointCloudComponentAdder_3
    COMPONENTS_TO_ADD = cat_sio,Int32,@Value(cat_sio)
    -> FeatureWriter_3 [File1]
FeatureWriter_3
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,DESTINATION_DATASETTYPE_VALIDATION,Yes,COORDINATE_SYSTEM_GRANULARITY,FEATURE,VERSION,1.2,USER_COMPONENTS,cat_sio
    FEATURE_TYPE_LIST_ATTR = _feature_type
    TOTAL_FEATURES_WRITTEN_ATTR = _total_features_written
    DATASET_ATTR = _dataset
    DATASET = C:\Trabajo_Ana\proceso_las_rioja\temp
    SUMMARY -> PythonCaller_3
PythonCaller_3
    PYTHONSYMBOL = processFeature
    PYTHONSOURCE:
      import fme
      import fmeobjects
      from subprocess import call


      # Template Function interface:
      # When using this function, make sure its name is set as the value of
      # the 'Class or Function to Process Features' transformer parameter
      def processFeature(feature):
          fichero_entrada = feature.getAttribute("_feature_type{0}.name") + ".laz"

          ruta_fichero_entrada = "c:/Trabajo_Ana/proceso_las_rioja/temp/" + fichero_entrada
          ruta_salida_ground = "c:/Trabajo_Ana/proceso_las_rioja/salida_ground/"
          ruta_salida_height = "c:/Trabajo_Ana/proceso_las_rioja/salida_height/"
          ruta_salida_classify = "c:/Trabajo_Ana/proceso_las_rioja/salida_classify/"

          ruta_fichero_entrada = ruta_fichero_entrada.replace("\/", "\\")
          print(ruta_fichero_entrada)

          num_cores = 3

      # lasground
          argumento = "lasground -i " + ruta_fichero_entrada
          argumento += " -odir " + ruta_salida_ground
          argumento += " -olaz "
          argumento += " -step 10 "
          argumento += " -stddev 1 "
          argumento += " -offset 0.05 "
          argumento += " -spike 1 "
          argumento += " -ignore_class 7 12 "
          argumento += " -non_ground_unchanged "
          # argumento += " -cores " + str(num_cores)

          resultado = call(argumento)
          if(resultado == 0):
              print("ground correcto")
          else:
              print("ground fallido")

      # lasheight
          argumento = "lasheight -i " + ruta_salida_ground + fichero_entrada
          argumento += " -odir " + ruta_salida_height
          argumento += " -olaz "
          argumento += " -classify_below -0.5 7 "
          argumento += " -classify_above 100.0 7 "
          argumento += " -classify_between 0 0.5 3 "
          argumento += " -classify_between 0.5 3 4 "
          argumento += " -classify_between 3 100.0 5 "
          argumento += " -ignore_class 7 12 "
          argumento += " -store_in_user_data "
          # argumento += " -cores " + str(num_cores)

          resultado = call(argumento)
          if(resultado == 0):
              print("height correcto")
          else:
              print("height fallido")

       # lasclassify
          argumento = "lasclassify -i " + ruta_salida_height + fichero_entrada
          argumento += " -odir " + ruta_salida_classify
          argumento += " -olaz "
          argumento += " -step 3 "
          argumento += " -planar 0.1 "
          argumento += " -ground_offset 2 "
          argumento += " -ignore_class 7 12 "
          # argumento += " -cores " + str(num_cores)

          resultado = call(argumento)
          if(resultado == 0):
              print("classify correcto")
          else:
              print("classify fallido")

          pass
    -> FeatureHolder
Note: Urbana
Note: prados
PointCloudFilter_2
    FILTER_TABLE = EXPRESSION_LIST @Value(city) ==  1 FILTER_ATTRIBUTE __pc_internal_filter_attribute__ FILTER_ATTRIBUTE_VALUES_LIST city 1
    OUTPUT_UNFILTERED_POINTS = Yes
    city 1 -> StringConcatenator_3
    <UNFILTERED> -> StringConcatenator_7
StringConcatenator_3
    VAL_ATTR = _filename
    ACTION = Create New Attribute
    PARM_LINE = @Value(fme_basename)_siose31
    -> PointCloudComponentAdder
Note: cat_sio
PointCloudComponentAdder
    COMPONENTS_TO_ADD = cat_sio,Int32,@Value(cat_sio)
    -> FeatureWriter_4 [File1]
FeatureWriter_4
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,DESTINATION_DATASETTYPE_VALIDATION,Yes,COORDINATE_SYSTEM_GRANULARITY,FEATURE,VERSION,1.2,FIXED_GROUP,FME_DISCLOSURE_CLOSED,USER_COMPONENTS,cat_sio
    FEATURE_TYPE_LIST_ATTR = _feature_type
    TOTAL_FEATURES_WRITTEN_ATTR = _total_features_written
    DATASET_ATTR = _dataset
    DATASET = C:\Trabajo_Ana\proceso_las_rioja\temp
    SUMMARY -> PythonCaller_4
PythonCaller_4
    PYTHONSYMBOL = processFeature
    PYTHONSOURCE:
      import fme
      import fmeobjects
      from subprocess import call


      # Template Function interface:
      # When using this function, make sure its name is set as the value of
      # the 'Class or Function to Process Features' transformer parameter
      def processFeature(feature):
          fichero_entrada = feature.getAttribute("_feature_type{0}.name") + ".laz"

          ruta_fichero_entrada = "c:/Trabajo_Ana/proceso_las_rioja/temp/" + fichero_entrada
          ruta_salida_ground = "c:/Trabajo_Ana/proceso_las_rioja/salida_ground/"
          ruta_salida_height = "c:/Trabajo_Ana/proceso_las_rioja/salida_height/"
          ruta_salida_classify = "c:/Trabajo_Ana/proceso_las_rioja/salida_classify/"

          ruta_fichero_entrada = ruta_fichero_entrada.replace("\/", "\\")
          print(ruta_fichero_entrada)

          num_cores = 3

      # lasground
          argumento = "lasground_new -i " + ruta_fichero_entrada
          argumento += " -odir " + ruta_salida_ground
          argumento += " -olaz "
          argumento += " -step 25 "
          argumento += " -stddev 1 "
          argumento += " -offset 0.05 "
          argumento += " -spike 0.50 "
          argumento += " -ignore_class 7 12 "
          argumento += " -non_ground_unchanged "
          # argumento += " -cores " + str(num_cores)

          resultado = call(argumento)
          if(resultado == 0):
              print("ground correcto")
          else:
              print("ground fallido")

      # lasheight
          argumento = "lasheight -i " + ruta_salida_ground + fichero_entrada
          argumento += " -odir " + ruta_salida_height
          argumento += " -olaz "
          argumento += " -classify_below -0.5 7 "
          argumento += " -classify_above 100.0 7 "
          argumento += " -classify_between 0 0.5 3 "
          argumento += " -classify_between 0.5 3 4 "
          argumento += " -classify_between 3 100.0 5 "
          argumento += " -ignore_class 7 12 "
          argumento += " -store_in_user_data "
          # argumento += " -cores " + str(num_cores)

          resultado = call(argumento)
          if(resultado == 0):
              print("height correcto")
          else:
              print("height fallido")

       # lasclassify
          argumento = "lasclassify -i " + ruta_salida_height + fichero_entrada
          argumento += " -odir " + ruta_salida_classify
          argumento += " -olaz "
          argumento += " -step 2 "
          argumento += " -planar 0.1 "
          argumento += " -ground_offset 2 "
          argumento += " -ignore_class 7 12 "
          # argumento += " -cores " + str(num_cores)

          resultado = call(argumento)
          if(resultado == 0):
              print("classify correcto")
          else:
              print("classify fallido")

          pass
    -> FeatureHolder
Note: casas aisladas
StringConcatenator_7
    VAL_ATTR = _filename
    ACTION = Create New Attribute
    PARM_LINE = @Value(fme_basename)_siose3
    -> PointCloudComponentAdder_6
Note: cat_sio
PointCloudComponentAdder_6
    COMPONENTS_TO_ADD = cat_sio,Int32,@Value(cat_sio)
    -> FeatureWriter_8 [File1]
FeatureWriter_8
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,COORDINATE_SYSTEM_GRANULARITY,FEATURE,DESTINATION_DATASETTYPE_VALIDATION,Yes,USER_COMPONENTS,cat_sio,FIXED_GROUP,FME_DISCLOSURE_CLOSED,VERSION,1.2
    FEATURE_TYPE_LIST_ATTR = _feature_type
    TOTAL_FEATURES_WRITTEN_ATTR = _total_features_written
    DATASET_ATTR = _dataset
    DATASET = C:\Trabajo_Ana\proceso_las_rioja\temp
    SUMMARY -> PythonCaller_8
PythonCaller_8
    PYTHONSYMBOL = processFeature
    PYTHONSOURCE:
      import fme
      import fmeobjects
      from subprocess import call


      # Template Function interface:
      # When using this function, make sure its name is set as the value of
      # the 'Class or Function to Process Features' transformer parameter
      def processFeature(feature):
          fichero_entrada = feature.getAttribute("_feature_type{0}.name") + ".laz"

          ruta_fichero_entrada = "c:/Trabajo_Ana/proceso_las_rioja/temp/" + fichero_entrada
          ruta_salida_ground = "c:/Trabajo_Ana/proceso_las_rioja/salida_ground/"
          ruta_salida_height = "c:/Trabajo_Ana/proceso_las_rioja/salida_height/"
          ruta_salida_classify = "c:/Trabajo_Ana/proceso_las_rioja/salida_classify/"

          ruta_fichero_entrada = ruta_fichero_entrada.replace("\/", "\\")
          print(ruta_fichero_entrada)

          num_cores = 3

      # lasground
          argumento = "lasground -i " + ruta_fichero_entrada
          argumento += " -odir " + ruta_salida_ground
          argumento += " -olaz "
          argumento += " -step 10 "
          argumento += " -stddev 1 "
          argumento += " -offset 0.05 "
          argumento += " -spike 1 "
          argumento += " -ignore_class 7 12 "
          argumento += " -non_ground_unchanged "
          # argumento += " -cores " + str(num_cores)

          resultado = call(argumento)
          if(resultado == 0):
              print("ground correcto")
          else:
              print("ground fallido")

      # lasheight
          argumento = "lasheight -i " + ruta_salida_ground + fichero_entrada
          argumento += " -odir " + ruta_salida_height
          argumento += " -olaz "
          argumento += " -classify_below -0.5 7 "
          argumento += " -classify_above 100.0 7 "
          argumento += " -classify_between 0 0.5 3 "
          argumento += " -classify_between 0.5 3 4 "
          argumento += " -classify_between 3 100.0 5 "
          argumento += " -ignore_class 7 12 "
          argumento += " -store_in_user_data "
          # argumento += " -cores " + str(num_cores)

          resultado = call(argumento)
          if(resultado == 0):
              print("height correcto")
          else:
              print("height fallido")

       # lasclassify
          argumento = "lasclassify -i " + ruta_salida_height + fichero_entrada
          argumento += " -odir " + ruta_salida_classify
          argumento += " -olaz "
          argumento += " -step 2 "
          argumento += " -planar 0.1 "
          argumento += " -ground_offset 2 "
          argumento += " -ignore_class 7 12 "
          # argumento += " -cores " + str(num_cores)

          resultado = call(argumento)
          if(resultado == 0):
              print("classify correcto")
          else:
              print("classify fallido")

          pass
    -> FeatureHolder
Note: Agua
Note: industrial
StringConcatenator_4
    VAL_ATTR = _filename
    ACTION = Create New Attribute
    PARM_LINE = @Value(fme_basename)_siose4
    -> PointCloudComponentAdder_2
Note: Añadimos el componente cat_sio
PointCloudComponentAdder_2
    COMPONENTS_TO_ADD = cat_sio,Int32,@Value(cat_sio)
    -> FeatureWriter_5 [File1]
Note: Almacenamos en el componente cat_sio
FeatureWriter_5
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,DESTINATION_DATASETTYPE_VALIDATION,Yes,COORDINATE_SYSTEM_GRANULARITY,FEATURE,VERSION,1.2,USER_COMPONENTS,cat_sio
    FEATURE_TYPE_LIST_ATTR = _feature_type
    TOTAL_FEATURES_WRITTEN_ATTR = _total_features_written
    DATASET_ATTR = _dataset
    DATASET = C:\Trabajo_Ana\proceso_las_rioja\temp
    SUMMARY -> PythonCaller_5
Note: En 'user_data' almacenamos el valor de height
PythonCaller_5
    PYTHONSYMBOL = processFeature
    PYTHONSOURCE:
      import fme
      import fmeobjects
      from subprocess import call


      # Template Function interface:
      # When using this function, make sure its name is set as the value of
      # the 'Class or Function to Process Features' transformer parameter
      def processFeature(feature):
          fichero_entrada = feature.getAttribute("_feature_type{0}.name") + ".laz"

          ruta_fichero_entrada = "c:/Trabajo_Ana/proceso_las_rioja/temp/" + fichero_entrada
          ruta_salida_ground = "c:/Trabajo_Ana/proceso_las_rioja/salida_ground/"
          ruta_salida_height = "c:/Trabajo_Ana/proceso_las_rioja/salida_height/"
          ruta_salida_classify = "c:/Trabajo_Ana/proceso_las_rioja/salida_classify/"

          ruta_fichero_entrada = ruta_fichero_entrada.replace("\/", "\\")
          print(ruta_fichero_entrada)

          num_cores = 3

      # lasground
          argumento = "lasground -i " + ruta_fichero_entrada
          argumento += " -odir " + ruta_salida_ground
          argumento += " -olaz "
          argumento += " -step 8 "
          argumento += " -stddev 1 "
          argumento += " -offset 0.05 "
          argumento += " -spike 1 "
          argumento += " -ignore_class 7 12 "
          argumento += " -non_ground_unchanged "
          # argumento += " -cores " + str(num_cores)

          resultado = call(argumento)
          if(resultado == 0):
              print("ground correcto")
          else:
              print("ground fallido")

      # lasheight
          argumento = "lasheight -i " + ruta_salida_ground + fichero_entrada
          argumento += " -odir " + ruta_salida_height
          argumento += " -olaz "
          argumento += " -classify_below -0.5 7 "
          argumento += " -classify_above 100.0 7 "
          argumento += " -classify_between 0 0.5 3 "
          argumento += " -classify_between 0.5 3 4 "
          argumento += " -classify_between 3 100.0 5 "
          argumento += " -ignore_class 7 12 "
          argumento += " -store_in_user_data "
          # argumento += " -cores " + str(num_cores)

          resultado = call(argumento)
          if(resultado == 0):
              print("height correcto")
          else:
              print("height fallido")

       # lasclassify
          argumento = "lasclassify -i " + ruta_salida_height + fichero_entrada
          argumento += " -odir " + ruta_salida_classify
          argumento += " -olaz "
          argumento += " -step 2 "
          argumento += " -planar 0.1 "
          argumento += " -ground_offset 2 "
          argumento += " -ignore_class 7 12 "
          # argumento += " -cores " + str(num_cores)

          resultado = call(argumento)
          if(resultado == 0):
              print("classify correcto")
          else:
              print("classify fallido")

          pass
    -> FeatureHolder
StringConcatenator_5
    VAL_ATTR = _filename
    ACTION = Create New Attribute
    PARM_LINE = @Value(fme_basename)_siose6
    -> PointCloudComponentAdder_5
Note: cat_sio
PointCloudComponentAdder_5
    COMPONENTS_TO_ADD = cat_sio,Int32,@Value(cat_sio)
    -> FeatureWriter_6 [File1]
Note: Almacenamos en el componente cat_sio
FeatureWriter_6
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,DESTINATION_DATASETTYPE_VALIDATION,Yes,COORDINATE_SYSTEM_GRANULARITY,FEATURE,VERSION,1.2,USER_COMPONENTS,cat_sio
    FEATURE_TYPE_LIST_ATTR = _feature_type
    TOTAL_FEATURES_WRITTEN_ATTR = _total_features_written
    DATASET_ATTR = _dataset
    DATASET = C:\Trabajo_Ana\proceso_las_rioja\temp
    SUMMARY -> PythonCaller_7
PythonCaller_7
    PYTHONSYMBOL = processFeature
    PYTHONSOURCE:
      import fme
      import fmeobjects
      from subprocess import call


      # Template Function interface:
      # When using this function, make sure its name is set as the value of
      # the 'Class or Function to Process Features' transformer parameter
      def processFeature(feature):
          fichero_entrada = feature.getAttribute("_feature_type{0}.name") + ".laz"

          ruta_fichero_entrada = "c:/Trabajo_Ana/proceso_las_rioja/temp/" + fichero_entrada
          ruta_salida_ground = "c:/Trabajo_Ana/proceso_las_rioja/salida_ground/"
          ruta_salida_height = "c:/Trabajo_Ana/proceso_las_rioja/salida_height/"
          ruta_salida_classify = "c:/Trabajo_Ana/proceso_las_rioja/salida_classify/"

          ruta_fichero_entrada = ruta_fichero_entrada.replace("\/", "\\")
          print(ruta_fichero_entrada)

          num_cores = 3

      # lasground
          argumento = "lasground -i " + ruta_fichero_entrada
          argumento += " -odir " + ruta_salida_ground
          argumento += " -olaz "
          argumento += " -step 30 "
          argumento += " -stddev 1 "
          argumento += " -offset 0.05 "
          argumento += " -spike 0.5 "
          argumento += " -ignore_class 7 12 "
          argumento += " -non_ground_unchanged "
          # argumento += " -cores " + str(num_cores)

          resultado = call(argumento)
          if(resultado == 0):
              print("ground correcto")
          else:
              print("ground fallido")

      # lasheight
          argumento = "lasheight -i " + ruta_salida_ground + fichero_entrada
          argumento += " -odir " + ruta_salida_height
          argumento += " -olaz "
          argumento += " -classify_below -0.5 7 "
          argumento += " -classify_above 100.0 7 "
          argumento += " -classify_between 0 0.5 3 "
          argumento += " -classify_between 0.5 3 4 "
          argumento += " -classify_between 3 100.0 5 "
          argumento += " -ignore_class 7 12 "
          argumento += " -store_in_user_data "
          # argumento += " -cores " + str(num_cores)

          resultado = call(argumento)
          if(resultado == 0):
              print("height correcto")
          else:
              print("height fallido")

       # lasclassify
          argumento = "lasclassify -i " + ruta_salida_height + fichero_entrada
          argumento += " -odir " + ruta_salida_classify
          argumento += " -olaz "
          argumento += " -step 2 "
          argumento += " -planar 0.3 "
          argumento += " -ground_offset 3 "
          argumento += " -ignore_class 7 12 "
          # argumento += " -cores " + str(num_cores)

          resultado = call(argumento)
          if(resultado == 0):
              print("classify correcto")
          else:
              print("classify fallido")

          pass
    -> FeatureHolder
PointCloudExpressionEvaluator_12
    EXPRESSION_TABLE = classification Auto 9
    RESULT -> StringConcatenator_6
StringConcatenator_6
    VAL_ATTR = _filename
    ACTION = Create New Attribute
    PARM_LINE = @Value(fme_basename)_siose7
    -> FeatureWriter_7 [File1]
Note: Almacenamos el las con la zonificación de la categoria 7 (Agua) / c:/Trabajo_Ana/proceso_las_rioja/salida_classify/
FeatureWriter_7
    LAS_COMPRESSION = LAZ
    LAS_VERSION = 1.2
    LAS_DESTINATION_DATASETTYPE_VALIDATION = Yes
    LAS_COORDINATE_SYSTEM_GRANULARITY = FEATURE
    LAS_USER_COMPONENTS = cat_sio
    FORMAT = LAS
    WRITER_DIRECTIVES = COMPRESSION,LAZ,DESTINATION_DATASETTYPE_VALIDATION,Yes,VERSION,1.2,COORDINATE_SYSTEM_GRANULARITY,FEATURE,USER_COMPONENTS,cat_sio
    FEATURE_TYPE_LIST_ATTR = _feature_type
    TOTAL_FEATURES_WRITTEN_ATTR = _total_features_written
    DATASET_ATTR = _dataset
    DATASET = c:/Trabajo_Ana/proceso_las_rioja/salida_classify
    SUMMARY -> FeatureHolder
FeatureHolder
    -> Counter
Note: Nos quedamos con un elemento
Counter
    CNT_ATTR = _count
    START = 1
    SCOPE = Global
    DOMAIN = counter
    -> AttributeFilter
AttributeFilter
    ATTR_VALUES = <EMPTY>,<MISSING>,<NULL>,<UNFILTERED>,1
    ATTR_NAME = _count
    1 -> WorkspaceRunner
WorkspaceRunner
    WORKSPACE_FILE = $(FME_MF_DIR)lidar_process_eliminar_buffer.fmw
    BLOCKING = Yes
    WORKSPACE_PARAMETERS = SourceDataset_LAS,C:\Trabajo_Ana\proceso_las_rioja\salida_classify\*.laz,SourceDataset_ESRISHAPE,U:\cartogra\Ana\Trabajo_ana\lidar_2016\siose\siose_lidar_ccaa_cuadricula_lidar.shp,DestDataset_LAS,C:\Trabajo_Ana\proceso_las_rioja\salida_classify_merge
    SUCCEEDED -> Terminator [off]
Terminator
    MESSAGE = Translation Terminated

Bookmark: Merge de archivos
Note: MERGE
PythonCaller
    PYTHONSYMBOL = processFeature
    PYTHONSOURCE:
      import fme
      import fmeobjects
      from subprocess import call
      import os


      # Template Function interface:
      # When using this function, make sure its name is set as the value of
      # the 'Class or Function to Process Features' transformer parameter
      def processFeature(feature):
          fichero_entrada = FME_MacroValues['SourceDataset_LAS'].replace(".laz", "")
          # Nos quedamos solo con el nombre del fichero, descartando el resto del path
          fichero_entrada = os.path.basename(fichero_entrada)

          print(fichero_entrada)

          ruta_entrada_classify = "c:/Trabajo_Ana/proceso_las_rioja/salida_classify/"
          ruta_salida_classify = "c:/Trabajo_Ana/proceso_las_rioja/salida_classify_merge/"

          num_cores = 3


      # lasmerge
          argumento = "lasmerge -i " + ruta_entrada_classify + fichero_entrada + "*.laz"
          argumento += " -odir " + ruta_salida_classify
          argumento += " -o " + fichero_entrada + "_merge.laz"
          print(argumento)
          resultado = call(argumento)
          if(resultado == 0):
              print("merge correcto")
          else:
              print("merge fallido")
    -> PythonCaller_6
Note: DELETE TEMPORARY FILES
PythonCaller_6
    PYTHONSYMBOL = processFeature
    PYTHONSOURCE:
      import fme
      import fmeobjects
      import os, shutil


      # Template Function interface:
      # When using this function, make sure its name is set as the value of
      # the 'Class or Function to Process Features' transformer parameter
      def processFeature(feature):
          # BORRADO TEMP
          folder = 'c:/Trabajo_Ana/proceso_las_rioja/temp/'
          print("Borrando..." + folder)
          for the_file in os.listdir(folder):
              file_path = os.path.join(folder, the_file)
              try:
                  if os.path.isfile(file_path):
                      os.unlink(file_path)
              except Exception as e:
                  print(e)

          # BORRADO GROUND
          folder = 'c:/Trabajo_Ana/proceso_las_rioja/salida_ground/'
          print("Borrando..." + folder)
          for the_file in os.listdir(folder):
              file_path = os.path.join(folder, the_file)
              try:
                  if os.path.isfile(file_path):
                      os.unlink(file_path)
              except Exception as e:
                  print(e)

          # BORRADO HEIGHT
          folder = 'c:/Trabajo_Ana/proceso_las_rioja/salida_height/'
          print("Borrando..." + folder)
          for the_file in os.listdir(folder):
              file_path = os.path.join(folder, the_file)
              try:
                  if os.path.isfile(file_path):
                      os.unlink(file_path)
              except Exception as e:
                  print(e)

          # BORRADO CLASSIFY (sin merge, por el CAT_SIO)
          folder = 'c:/Trabajo_Ana/proceso_las_rioja/salida_classify/'
          print("Borrando..." + folder)
          for the_file in os.listdir(folder):
              file_path = os.path.join(folder, the_file)
              try:
                  if os.path.isfile(file_path):
                      os.unlink(file_path)
              except Exception as e:
                  print(e)
