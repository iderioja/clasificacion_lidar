FME workspace Convert_GRD_from Ngrid.fmw

Parameters:
- DestDataset_TEXTLINE = $(FME_MF_DIR)GridData\EGM08_REDNAP.grd   # Destination Text File

Readers:
- NGRID_1: NGRID from $(FME_MF_DIR)official\EGM08_REDNAP.grd

Writers:
- TEXTLINE_1: TEXTLINE to $(DestDataset_TEXTLINE)

Note: NGRID: EGM08_REDNAP oficial del IGN / ftp://ftp.geodesia.ign.es/geoide/GRD/)
NGRID (reader NGRID_1)
    -> RasterPropertiesExtractor
RasterPropertiesExtractor
    -> AttributeCreator_2
    -> AttributeCreator_7
    -> RasterCellCoercer
Note: Spacer
AttributeCreator_2
    ATTR_LIST = _sort,1,text_line_data,""
    -> Sorter
Sorter
    SORT_PARM = _sort NUMERIC ASCENDING
    SORTED -> text_line (writer TEXTLINE_1)
Note: archivo GRD en formato texto
text_line (writer TEXTLINE_1)
    attributes: text_line_data buffer

Bookmark: Header
Note: Información de cabecera
Note: Adjust min/max to pixel centers
AttributeCreator_7
    ATTR_LIST = _min_x,@Evaluate(@Value(_min_x)+(@Value(_spacing_x)*0.5)),_min_y,@Evaluate(@Value(_min_y)+(@Value(_spacing_y)*0.5)),_max_x,@Evaluate(@Value(_max_x)-(@Value(_spacing_x)*0.5)),_max_y,@Evaluate(@Value(_max_y)-(@Value(_spacing_y)*0.5))
    -> StringFormatter
StringFormatter
    SRC_ATTRS = _spacing_x,_spacing_y,_min_x,_min_y,_max_x,_max_y
    FORMAT = 05.8f
    -> StringFormatter_2
StringFormatter_2
    SRC_ATTRS = _spacing_x,_spacing_y,_min_x,_min_y,_max_x,_max_y
    FORMAT = 12s
    -> AttributeCreator
AttributeCreator
    ATTR_LIST = _sort,0,text_line_data, @Value(_min_y)@Value(_max_y)@Value(_min_x)@Value(_max_x)@Value(_spacing_y)@Value(_spacing_x)
    -> Sorter

Bookmark: Grid Values
Note: Información de la malla
RasterCellCoercer
    CELL_GEOMETRY = Points
    EXTRACT_NODATA = Yes
    PRESERVE_ATTRIBUTES = No
    COL_ATTR = _column
    ROW_ATTR = _row
    EXTRACT_BAND_VALUES_AS = Attributes
    -> Tester
Tester
    TEST_CLAUSE = TEST @Value(_band{0}.value) < 10000000
    TEST_MODE = Automatic
    BOOL_OP = OR
    TEST_DESCRIPTION = ""
    PASSED -> AttributeCreator_3
    FAILED -> AttributeCreator_4
AttributeCreator_3
    ATTR_LIST = value,@Value(_band{0}.value)
    -> StringFormatter_3
AttributeCreator_4
    ATTR_LIST = value,0
    -> StringFormatter_3
StringFormatter_3
    SRC_ATTRS = value
    FORMAT = 3.3f
    -> StringFormatter_4
StringFormatter_4
    SRC_ATTRS = value
    FORMAT = 9s
    -> Sorter_2
Sorter_2
    SORT_PARM = _row NUMERIC ASCENDING _column NUMERIC ASCENDING
    SORTED -> Counter
Counter
    SCOPE = Global
    CNT_ATTR = _count
    DOMAIN = counter
    START = 0
    -> AttributeCreator_6
AttributeCreator_6
    ATTR_LIST = _mod_count,@Evaluate(@Value(_count)/8)
    -> Aggregator
Aggregator
    GROUP_BY = _mod_count
    AGGREGATE_TYPE = Homogeneous Collection (If Possible)
    MODE = Assemble One Level
    ACCUM_ATTRS_NAME = No
    LIST_NAME = _list
    SEP = ,
    ORDERED = No
    AGGREGATE -> ListSorter
ListSorter
    ORDER = Increasing
    TYPE = Numeric
    SRC_LIST = _list{}._count
    -> ListConcatenator
ListConcatenator
    LIST_ATTR = _list{}.value
    DROP_EMPTY_PARTS = No
    VAL_ATTR = _concatenated
    -> AttributeCreator_5
AttributeCreator_5
    ATTR_LIST = text_line_data, @Value(_concatenated),_sort,@Evaluate(@Value(_mod_count)+5)
    -> Sorter
